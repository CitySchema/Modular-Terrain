FME workspace Batch_SKP_Worksheet_Runner.fmw

Parameters:
- SourceDataset_SHAPEFILE = F:\current_work\projects\Boston\Bos3d\Bos3dDevpbc\Workflows\create_grid\TileExporter_Data\Bos3d_Tile_Polys.shp   # Source Esri Shapefile(s)

Readers:
- SHAPEFILE_1: SHAPEFILE from $(SourceDataset_SHAPEFILE)

Bos3d_Tile_Polys (reader SHAPEFILE_1)
    attributes: tile_id char(25), tile_label char(10), town char(50), grid_col char(10), grid_row char(10), town_code char(10), BosShift_X long, BosShift_Y long, Lat double, Lon double, MASP_X long, MASP_Y long, Shape_Leng double, Shape_Area double
    -> WorkspaceRunner
Note: Set runner parameters to identify the workspace to run. And also to use the value of Tile_ID for each go-around.
WorkspaceRunner
    BLOCKING = No
    MAX_PROC = 4
    MAX_TO_BATCH = 1
    WORKSPACE_FILE = $(FME_MF_DIR)Draped_Terrain_OBJ_DEV.fmw
    WORKSPACE_PARAMETERS = Tile_Name,@Value(tile_id),DestinationFolder,F:\current_work\projects\Boston\Bos3d\Bos3dDevpbc\Bos3d_City_Model_Stage\Bos3d_Tiled_Data\Bos3d_TerrainMesh_2011_OBJ_test
    FAILED -> WorkspaceRunner_Failed
    SUMMARY -> WorkspaceRunner_Summary
WorkspaceRunner_Failed: Logger
    LOG_FEATURE = LOG_ONLY
    MAXCOORDS = 20
    MAXFEATS = 20
    MESSAGE = Feature is:
    SEVERITY = INFO
WorkspaceRunner_Summary: Logger
    LOG_FEATURE = LOG_ONLY
    MAXCOORDS = 20
    MAXFEATS = 20
    MESSAGE = Feature is:
    SEVERITY = INFO
