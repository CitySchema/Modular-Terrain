FME workspace Draped_Terrain_OBJ.fmw

Parameters:
- Tile_Name = BOS_H_3
- tiled_datasets_folder = F:\current_work\projects\metro_3d\metro3d_terrain\output
- SourceDataset_JPEG = $(tiled_datasets_folder)\BOS3d_Groundplan_2011_JPG\$(Tile_Name)_Groundplan_2011.jpg   # Source JPEG File(s)
- DestDataset_OBJ = $(DestinationFolder)\$(Tile_Name)_Terrain_2011_OBJ.zip   # Destination OBJ Folder
- Tiled_GIS_Folder = $(tiled_datasets_folder)\tiled_gis
- DestinationFolder = $(tiled_datasets_folder)\Bos3d_TerrainMesh_2011_OBJ   # Destination Folder
- SourceDataset_SHAPEFILE_3 = $(Tiled_GIS_Folder)\$(Tile_Name)_GIS\TinTriangle.shp   # Source Esri Shapefile(s)

Readers:
- JPEG_1: JPEG from $(SourceDataset_JPEG)
- SHAPEFILE_1: SHAPEFILE from $(SourceDataset_SHAPEFILE_3)

Writers:
- OBJ_1: OBJ to $(DestDataset_OBJ)

Note: This workbench takes TIN triangles that have been created in ArcGIS and converts them to an FME mesh. It drapes a pre-cliped groundplan image and then converts to an OBJ that has bee properly rotated and shifted to sit well with theother datasets in the metropolian area model collection. Maybe one day, the FME TIN creator wil work as well as the ESRI one. Last time I checked, it created incorrect fences along the edges of tiles.
TinTriangle (reader SHAPEFILE_1)
    attributes: Slope_Pct double, Aspect double, Tri_Index long
    -> FaceReplacer
Note: Converts polygons to faces that can become4 part of a mesh and accept textures.
FaceReplacer
    ANGULAR_TOLERANCE = 0.0
    ANGULAR_TOLERANCE_CHOICE = Automatic
    THICKNESS_TOLERANCE = 0.0
    THICKNESS_TOLERANCE_CHOICE = Automatic
    -> Aggregator
Note: Merges the faces into a single mesh object
Aggregator
    ACCUM_ATTRS_NAME = Use Attributes From One Feature
    AGGREGATE_TYPE = Homogeneous Collection (If Possible)
    MODE = Geometry - Assemble One Level
    SEP = ,
    AGGREGATE -> AppearanceSetter [GEOMETRY]
JPEG (reader JPEG_1)
    -> AppearanceSetter [APPEARANCE]
Note: Drape the Basemap
AppearanceSetter
    APPEARANCE_NAME = $(Tile_Name)_Basemap_2011
    DEF_STORAGE = Create New Definitions
    GQUERY:
      for $geom in //geometry
      where $geom/count(parent::geometry) = 0
      return number($geom/@fme_id)
    SET_ON_SIDE = Front and Back Sides
    TEXTURE_MAPPING_TYPE_CHOICE = From Top View
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> Offsetter
Note: Our OBJs have Z up and Y forward. This is not the default for OBJs
tin_triangles (writer OBJ_1)

Bookmark: OBJ Rotation and offset
Offsetter
    MODE = Cartesian Coordinate
    XOFF = -731100
    YOFF = -2902900
    ZOFF = 0
    OFFSET -> 3DRotator
    OFFSET -> tin_triangles (writer OBJ_1)
Note: This offset converts Mass State Plane Feet to our Boston Shifted coordinate systemm
3DRotator [off]
    ANGLE = -90
    AXIS_CHOICE = X Axis
